Attribute VB_Name = "Module1"
Sub NodeInCell()
    Dim TempEle As Element
    Dim tnEle As TextNodeElement
    Dim cEle As CellElement
    Dim sArray() As Element
    Dim s As Long
    Dim tEE As ElementEnumerator
    Dim oEE As ElementEnumerator
    Dim oSC As ElementScanCriteria
    Dim sStart As Long
    Dim sEnd As Long

    Set oSC = New ElementScanCriteria
    oSC.ExcludeAllTypes
    oSC.IncludeType msdElementTypeCellHeader
    Set oEE = ActiveModelReference.Scan(oSC)
    sArray = oEE.BuildArrayFromContents
    sStart = LBound(sArray)
    sEnd = UBound(sArray)

    For s = sStart To sEnd
        Set cEle = sArray(s)
        Do While cEle.MoveToNextElement
            Set TempEle = cEle.CopyCurrentElement
            If TempEle.Type = msdElementTypeTextNode Then
                Set tnEle = TempEle
                Set tEE = tnEle.GetSubElements
                Do While tEE.MoveNext
                    ' Here, you can add conditions to check and modify the text values.
                    ' For example, you can check if the text is "1" and increment it.
                    ' If tEE.Current.AsTextElement.Text = "1" Then
                    tEE.Current.AsTextElement.Text = CStr(CInt(tEE.Current.AsTextElement.Text) + 1)
                    tEE.Current.Rewrite
                    ActiveModelReference.AddElement cEle
                    ' End If
                Loop
            End If
        Loop
    Next s
End Sub
